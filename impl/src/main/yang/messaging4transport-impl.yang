module messaging4transport-impl {
    yang-version 1;
    namespace "urn:opendaylight:params:xml:ns:yang:messaging4transport:impl";
    prefix "messaging4transport-impl";

    import config { prefix config; revision-date 2013-04-05; }
    import opendaylight-md-sal-binding { prefix md-sal-binding; revision-date 2013-10-28;}
    import opendaylight-md-sal-dom { prefix md-sal-dom; revision-date 2013-10-28;}

    description
        "Service definition for messaging4transport project";

    revision "2014-12-10" {
        description
            "Initial revision";
    }

    identity messaging4transport {
        base config:module-type;
        config:java-name-prefix Messaging4transport;
    }

    augment "/config:modules/config:module/config:configuration" {
        case messaging4transport {
            when "/config:modules/config:module/config:type = 'messaging4transport'";
            container broker {
                uses config:service-ref {
                    refine type {
                        mandatory true;
                        config:required-identity md-sal-binding:binding-broker-osgi-registry;
                    }
                }
            }
            container dom-broker {
                uses config:service-ref {
                    refine type {
                        mandatory true;
                        config:required-identity md-sal-dom:dom-broker-osgi-registry;
                    }
                }
            }
            container dom-schema-service {
                uses config:service-ref {
                    refine type {
                        mandatory true;
                        config:required-identity md-sal-dom:schema-service;
                    }
                }
            }
        }
    }
}
